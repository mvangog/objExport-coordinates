Attribute VB_Name = "ForcedOrigin"
Dim modalHandler As New Macro2ModalHandler
Public Sub onprojectload()
    Dim startPoint As Point3d
    Dim point As Point3d, point2 As Point3d
    Dim lngTemp As Long


    AddModalDialogEventsHandler modalHandler

End Sub

Sub ExportOBJ()

''  if this function is used, we don't want the modalHandler active all the time
''  therefore we remove the modalHandler that was attached during onprojectload
    RemoveModalDialogEventsHandler modalHandler
    AddModalDialogEventsHandler modalHandler
    
        CadInputQueue.SendCommand "MDL KEYIN objexport dialog obj"

    RemoveModalDialogEventsHandler modalHandler
    CommandState.StartDefaultCommand
    
End Sub

Public Sub onprojectunload()
RemoveModalDialogEventsHandler modalHandler
End Sub

Attribute VB_Name = "Macro2ModalHandler"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IModalDialogEvents

Dim Lijn As LineElement


Private Sub IModalDialogEvents_OnDialogClosed(ByVal DialogBoxName As String, ByVal DialogResult As MsdDialogBoxResult)
    If DialogBoxName = "OBJ Export Settings" Then
        ActiveModelReference.RemoveElement Lijn
        CadInputQueue.SendCommand "VIEW PREVIOUS"
    End If
End Sub

Private Sub IModalDialogEvents_OnDialogOpened(ByVal DialogBoxName As String, DialogResult As MsdDialogBoxResult)

    If DialogBoxName = "OBJ Export Settings" Then
        createPoint
    '   Remove the following line to let the user close the dialog box.
     '   DialogResult = msdDialogBoxResultOK

    End If  ' OBJ Export Settings

End Sub

Private Sub createPoint()
''creates a pointElement at position 0,0,0
''selects the created point
''does a Fit view, so the point and the 3d-model are both in view
''if the point is not in view, micrsotation wil not use it as originpoint
 Dim point As Point3d
    point.X = 0
    point.Y = 0
    point.Z = 0
    Dim lijntje(0 To 1) As Point3d
    lijntje(0) = point
    lijntje(1) = point
    
    Set Lijn = CreateLineElement1(Nothing, lijntje)
    ActiveModelReference.AddElement Lijn
    Lijn.Rewrite
    ActiveModelReference.UnselectAllElements
    ActiveModelReference.SelectElement Lijn, True
    CadInputQueue.SendCommand "FIT VIEW EXTENDED"

End Sub
